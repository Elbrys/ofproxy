module ofproxyapp-impl {
    yang-version 1;
    namespace "urn:opendaylight:params:xml:ns:yang:ofproxyapp:impl";
    prefix "ofproxyapp-impl";

    import config { prefix config; revision-date 2013-04-05; }
    import opendaylight-md-sal-binding { prefix md-sal-binding; revision-date 2013-10-28;}

    description
        "Service definition for ofproxy project";

    revision "2015-06-17" {
        description
            "Initial revision";
    }

    identity ofproxyapp {
        base config:module-type;
        config:java-name-prefix OFProxyapp;
    }

    augment "/config:modules/config:module/config:configuration" {
        case ofproxyapp {
            when "/config:modules/config:module/config:type = 'ofproxyapp'";
            container broker {
                uses config:service-ref {
                    refine type {
                        mandatory true;
                        config:required-identity md-sal-binding:binding-broker-osgi-registry;
                    }
                }
            }
           //Wires dependent services into this class - in this case the RPC registry service
           container rpc-registry {
               uses config:service-ref {
                   refine type {
                       mandatory true;
                       config:required-identity md-sal-binding:binding-rpc-registry;
                   }
               }
           } 
        }
    }
}
